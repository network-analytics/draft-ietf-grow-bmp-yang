module ietf-bmp-ni-deviations {
  yang-version 1.1;
  namespace "urn:ietf:params:xml:ns:yang:ietf-bmp-ni-deviations";
  prefix bmp-dev;

  import ietf-bmp {
    prefix bmp;
  }

  organization
    "IETF GROW Working Group";
  contact
    "WG Web:   <https://datatracker.ietf.org/wg/grow/>
     WG List:  <mailto:grow@ietf.org>

     Author:  Camilo Cardona
        <mailto:camilo@ntt.net>

     Author:  Paolo Lucente
        <mailto:paolo@ntt.net>

     Author:  Thomas Graf
        <mailto:thomas.graf@swisscom.com>

     Author:  Benoit Claise
        <mailto:benoit@everything-ops.net>

     Author:  Dhananjay Patki
        <mailto:dhpatki@cisco.com>

     Author:  Prasad S. Narasimha
        <mailto:snprasad@cisco.com>";

  description
    "This module specifies a structure for BMP
     (BGP Monitoring Protocol) configuration and monitoring.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC 9196
     (https://www.rfc-editor.org/info/rfc9196); see the RFC itself
     for full legal notices.";

  revision 2025-06-09 {
    description
      "Change id type from string to leafref.";
    reference
      "RFC YYYY: BMP YANG Module
       RFC-EDITOR: please update YYYY with this RFC ID";
  }

  // Deviation: network-instance in bmp-ip-connection/active
  deviation "/bmp:bmp/bmp:monitoring-stations/bmp:monitoring-station/bmp:connection/bmp:passive-or-active/bmp:active/bmp:active/bmp:network-instance" {
    description
      "Change type to string instead of leafref to network-instance name.";
    deviate replace {
      type string;
    }
  }

  // Deviation: network-instance in bmp-ip-connection/passive
  deviation "/bmp:bmp/bmp:monitoring-stations/bmp:monitoring-station/bmp:connection/bmp:passive-or-active/bmp:passive/bmp:passive/bmp:network-instance" {
    description
      "Change type to string instead of leafref to network-instance name.";
    deviate replace {
      type string;
    }
  }

  // Deviation: id in route-monitoring
  deviation "/bmp:bmp/bmp:monitoring-stations/bmp:monitoring-station/bmp:bmp-data/bmp:route-monitoring/bmp:network-instance-configuration/bmp:network-instances/bmp:network-instance/bmp:id" {
    description
      "Change type to string instead of leafref to network-instance name.";
    deviate replace {
      type string;
    }
  }

}
