module ietf-bmp-bgp-dependencies {
  yang-version 1.1;
  namespace "urn:ietf:params:xml:ns:yang:ietf-bmp-bgp-dependencies";
  prefix bmp-bgp;

  import ietf-bmp {
    prefix bmp;
  }
  import ietf-routing {
    prefix rt;
    reference
      "RFC 8349: A YANG Data Model for Routing Management
       (NMDA Version).";
  }
  import ietf-bgp {
    prefix bgp;
    reference
      "I-D.draft-ietf-idr-bgp-model-17:
       BGP YANG module for Service Provider Network.";
  }
  import iana-bgp-types {
    prefix bt;
    reference
      "RFC AAAA: BGP YANG module for Service Provider Network.
       RFC-EDITOR: please update XXX with the RFC ID assigned
       to I-D.ietf-idr-bgp-model";
  }

  organization
    "IETF GROW Working Group";
  contact
    "WG Web:   <https://datatracker.ietf.org/wg/grow/>
     WG List:  <mailto:grow@ietf.org>

     Author:  Camilo Cardona
        <mailto:camilo@ntt.net>

     Author:  Paolo Lucente
        <mailto:cpaolo@ntt.net>

     Author:  Thomas Graf
        <mailto:thomas.graf@swisscom.com>

     Author:  Benoit Claise
        <mailto:benoit.claise@huawei.com>";
  description
    "This module specifies a structure for BMP
     (BGP Monitoring Protocol) configuration and monitoring.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC 9196
     (https://www.rfc-editor.org/info/rfc9196); see the RFC itself
     for full legal notices.";

  revision 2025-01-02 {
    description
      "initial version";
    reference
      "RFC YYYY: BMP YANG Module
       RFC-EDITOR: please update YYYY with this RFC ID";
  }

  grouping bmp-ni-peer-ribs-filter {
    description
      "Containers for configuring RIBs under the ietf-bgp:bgp
       container.";
    container address-families {
      description
        "container for lists of address-families";
      list address-family {
        key "id";
        description
          "List of address families.
           The name of the address family, as defined
           in the BGP model is used for keying.";
        leaf id {
          type identityref {
            base bt:afi-safi-type;
          }
          description
            "Address family id to configure";
        }
        leaf enabled {
          type boolean;
          default "true";
          description
            "Enables route monitoring messages
             for the address family";
        }
        container peers-configurations {
          description
            "Every peer under the configured network instance can be
             at most configured by one of the next containers.
             If the peer is not covered by any, then no BMP
             message should include information from/to that
             peer. If the peer is covered by more than one,
             then the priority is:

             1. peers
             2. peer-groups
             3. peer-type
             4. bmp-peer-selectors

             New child containers or new bmp-peer-selectors instances
             SHOULD provide a way of unambiguously selecting which
             configuration container should be selected for a peer in
             case multiple matches.
            ";
          container bmp-peer-selectors {
            description
              "Generic identification of peers to configure.";
            list bmp-peer-selector {
              key "id";
              description
                "Identification of peers
                 for which we send BMP data to the collector
                 using a peer type defined using a peer-types-bmp.
                 For instance, to create a default for all
                 peers use all-peers";
              leaf id {
                type identityref {
                  base bmp:bmp-peer-selectors;
                }
                description
                  "Peers to configure using a BMP peer selector";
              }
              leaf enabled {
                type boolean;
                default "true";
                description
                  "Enables routing monitoring messages
                   for the peer(s).";
              }
              uses bmp:route-monitoring-peer-grouping;
            }
          }
          container peer-types {
            description
              "Generic identification of peers to configure.";
            list peer-type {
              key "peer-type-id";
              description
                "Identification of peers
                 for which we send BMP data to the collector
                 using BGP peer-type (e.g. internal, external)
                ";
              leaf peer-type-id {
                type bt:peer-type;
                description
                  "BGP Peer type to configure";
              }
            }
            leaf enabled {
              type boolean;
              default "true";
              description
                "Enables routing monitoring messages
                 for the peer(s).";
            }
            uses bmp:route-monitoring-peer-grouping;
          }
          container peer-groups {
            description
              "Identification of peer-groups
               to configure";
            list peer-group {
              key "peer-group";
              description
                "Identification of peer-groups
                 for which we send BMP data to the collector";
              leaf peer-group {
                type leafref {
                  path "../../../../../../../../../../../"
                     + "bgp:peer-groups/bgp:peer-group/"
                     + "bgp:name";
                }
                description
                  "Peergroup to configure";
              }
              leaf enabled {
                type boolean;
                default "true";
                description
                  "Enables routing monitoring messages
                   for the peer-group(s).";
              }
              uses bmp:route-monitoring-peer-grouping;
            }
          }
          container peers {
            description
              "Identification of peers
               for which we send BMP data to the collector";
            list peer {
              key "id";
              description
                "Identification of peers
                 for which we send BMP data to the collector";
              leaf id {
                type leafref {
                  path "../../../../../../../../../../../"
                     + "bgp:neighbors/bgp:neighbor/"
                     + "bgp:remote-address";
                }
                description
                  "Peer to configure";
              }
              leaf enabled {
                type boolean;
                default "true";
                description
                  "Enables routing monitoring messages
                   for the peer(s).";
              }
              uses bmp:route-monitoring-peer-grouping;
            }
          }
        }
      }
    }
  }

  // Augment the BGP module to include data for network instances

  augment "/rt:routing/rt:control-plane-protocols/"
        + "rt:control-plane-protocol/bgp:bgp" {
    description
      "Augments the BGP container under control-plane-protocol.  It
       can be used to configure the global BGP instance, but also the
       network-instances under the module ietf-network-instance";
    container bmp-data {
      description
        "Container for the configuration of BMP data
         related to this BGP instance";
      container monitoring-stations {
        presence "If this container exists, the network
                  instance must be configured using this";
        description
          "Container for the configuration of BMP data
           related to this BGP instance";
        list monitoring-station {
          key "id";
          description
            "Container for the configuration of BMP data for this
             monitoring-station related to this BGP instance";
          leaf id {
            // TODO: We have not been able to configure
            // the schema mount to recognize this yet. 
            // Until we solve it, we will keep it as it is.
            //type leafref {
            //  path "/bmp:bmp/bmp:monitoring-stations/"
            //        + "bmp:monitoring-station/bmp:id";
            //}
            type string;
            description
              "Identification string for the monitoring station";
          }
          container route-monitoring {
            presence "The presence of this container means the
                      Network instance it contains MUST
                      be configured using it";
            description
              "Configuration of the data sources for
               route-monitoring messages for this network-instance";
            leaf enabled {
              type boolean;
              default "true";
              description
                "Enables routing monitoring
                 messages for the network instance.";
            }
            container adj-rib-in-pre {
              description
                "Configuration for the adj-rib-in pre-policy";
              reference
                "RFC7854: BGP Monitoring Protocol (BMP), Section 2.";
              uses bmp-ni-peer-ribs-filter;
            }
            container adj-rib-in-post {
              description
                "Configuration for the adj-rib-in post-policy";
              reference
                "RFC7854: BGP Monitoring Protocol (BMP), Section 2.";
              uses bmp-ni-peer-ribs-filter;
            }
            container local-rib {
              description
                "Configuration for the local-rib";
              reference
                "RFC9069: Support for Local RIB in the BGP Monitoring
                 Protocol (BMP), Section 3.";
              container address-families {
                description
                  "List of address families to enable for
                   local-rib.";
                list address-family {
                  key "id";
                  description
                    "Address family to enable for local-rib";
                  leaf id {
                    type identityref {
                      base bt:afi-safi-type;
                    }
                    description
                      "Address family id to enable for local-rib";
                  }
                  uses bmp:route-monitoring-peer-grouping;
                }
              }
            }
            container adj-rib-out-pre {
              description
                "Configuration for the adj-rib-out pre-policy";
              reference
                "RFC8671: Support for Adj-RIB-Out in the BGP
                 Monitoring Protocol (BMP) , Section 3.";
              uses bmp-ni-peer-ribs-filter;
            }
            container adj-rib-out-post {
              description
                "Configuration for the adj-rib-out post-policy";
              reference
                "RFC8671: Support for Adj-RIB-Out in the BGP
                 Monitoring Protocol (BMP) , Section 3.";
              uses bmp-ni-peer-ribs-filter;
            }
          }
        }
      }
    }
  }
}
